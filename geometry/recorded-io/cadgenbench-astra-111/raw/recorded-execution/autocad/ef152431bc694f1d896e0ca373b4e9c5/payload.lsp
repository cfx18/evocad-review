(vl-load-com)
(setvar "FILEDIA" 0)
(setvar "CMDECHO" 1)
(command "_.ACISIN" "[private value removed]")
(setq solids (ssget "_X" '((0 . "3DSOLID"))))
(princ (strcat "\nSAT_REIMPORT_SOLID_COUNT=" (itoa (sslength solids))))
(command "_.SOLIDEDIT" "_Body" "_Check" (ssname solids 0))
(repeat 4 (if (> (getvar "CMDACTIVE") 0) (command "_Exit")))
(princ "\nSAT_ROUNDTRIP_DONE")
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
