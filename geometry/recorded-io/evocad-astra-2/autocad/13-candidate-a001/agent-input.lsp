(setvar "CMDECHO" 0) (setvar "OSMODE" 0) (setvar "DELOBJ" 1) (setvar "INSUNITS" 4) (setvar "SOLIDHIST" 0) (command "_.UCS" "_World")
(defun ck (tag / ss) (setq ss (ssget "_X" '((0 . "3DSOLID")(410 . "Model")))) (if (or (null ss) (/= (sslength ss) 1)) (progn (princ (strcat "\nFAIL_SOLID_COUNT:" tag)) (exit))) (princ (strcat "\nPASS_3DSOLID:" tag " HANDLE=" (cdr (assoc 5 (entget (ssname ss 0)))))) (command "_.MASSPROP" ss "" "_No") (ssname ss 0))
(defun bx (a b h) (command "_.BOX" "_non" a "_non" b h) (entlast))
(defun cyl (a r b) (command "_.CYLINDER" "_non" a r "_Axis" "_non" b) (entlast))
(defun sub1 (body cutter tag) (command "_.SUBTRACT" body "" cutter "") (ck tag))

(setq body (ck "complete_model"))
(command "_.SOLIDEDIT" "_Body" "_Check" body "_eXit" "_eXit")
(command "_.AUDIT" "_Yes")
(setq allmodel (ssget "_X" '((410 . "Model"))))
(if (/= (sslength allmodel) 1) (progn (princ "\nFAIL_EXTRA_MODEL_ENTITIES") (exit)))
(if (/= (cdr (assoc 0 (entget (ssname allmodel 0)))) "3DSOLID") (progn (princ "\nFAIL_NOT_3DSOLID") (exit)))
(command "_.VPOINT" '(1 -1 1))
(command "_.ZOOM" "_Extents")
(ck "FINAL_SINGLE_NATIVE_EDITABLE_SOLID")
(princ "\nFINAL_VALIDATION_COMPLETE")
(princ)
