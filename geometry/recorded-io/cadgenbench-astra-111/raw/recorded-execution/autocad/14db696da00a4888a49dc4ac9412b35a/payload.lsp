(vl-load-com)
(setvar "CMDECHO" 0)
(setvar "FILEDIA" 0)
(setvar "OSMODE" 0)
(setvar "INSUNITS" 4)
(setvar "DELOBJ" 1)
(setvar "FACETRES" 10)
(setvar "ISOLINES" 0)
(defun poly (vs z / data v)
 (setq data (list '(0 . "LWPOLYLINE") '(100 . "AcDbEntity") '(100 . "AcDbPolyline") (cons 90 (length vs)) '(70 . 1) (cons 38 z)))
 (foreach v vs (setq data (append data (list (cons 10 (list (car v) (cadr v))) (cons 42 (caddr v))))))
 (entmakex data)
)
(defun prism (vs z h / e)
 (setq e (poly vs z))
 (command "_.EXTRUDE" e "" h)
 (entlast)
)
(defun cyl (x y z r h / e)
 (command "_.CYLINDER" (list x y z) r h)
 (entlast)
)
(defun cut (e) (command "_.SUBTRACT" body "" e ""))
(defun addsolid (e) (command "_.UNION" body e "") (setq body (entlast)))
(defun getbody () (ssname (ssget "_X" '((0 . "3DSOLID"))) 0))
(defun xcyl (x y z r h / e)
 (setq e (cyl 0 0 0 r h))
 (command "_.ROTATE3D" e "" "_Yaxis" '(0 0 0) 90)
 (command "_.MOVE" e "" '(0 0 0) (list x y z))
 e
)

(setq body (prism '((153.7 132.5 0) (129.7 132.5 -0.0330112) (121 128.2 0) (52 120 -0.2750539) (40.0795042 123.3520302 0.2820292) (-91.7117495 91.7117495 -0.4549736) (-131 96 -0.2267891) (-132.9 102.95 0.2920457) (-134.2 120.1 -0.1689489) (-135 124 0) (-135 132.5 0) (-158.5 132.5 0) (-158.5 124 -0.1687389) (-160 119.8 0.3616816) (-158.5 99.3 0) (-158.5 93 0.2521176) (-153 84 0) (-122 53 -0.3529412) (-123.5 29 0.0993987) (-129.7 0 0) (-129.7 -55.8 0.0890449) (-118 -111 0) (-118 -143 0.4142136) (-110 -152.9 0) (-71.5 -191.4 0.2211811) (-68 -192.9 0) (68 -192.9 0.2211811) (71.5 -191.4 0) (110 -152.9 0.1698243) (122 -122 0) (134.7 -105 0) (134.7 105 -0.5293802) (145 117 0) (149.5 117 0) (153.7 125 0)) 0 80))
(cut (prism '((92 0 1) (-92 0 0) (-92 -55.8 1) (92 -55.8 0)) -1 82))
(princ "\nSTAGE01_BODY_DONE")
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
