(progn
(setvar "CMDECHO" 0)
(setvar "OSMODE" 0)
(setvar "FILEDIA" 0)
(setvar "INSUNITS" 4)
(setvar "MEASUREMENT" 1)
(setvar "DELOBJ" 1)
(setvar "ISOLINES" 6)
(command "_.UCS" "_World")
(defun mkbox (x0 y0 z0 x1 y1 z1) (command "_.BOX" (list x0 y0 z0) (list x1 y1 z0) (- z1 z0)) (entlast))
(setq blank (mkbox 0.0 0.0 0.0 23.0 64.0 22.1))
(setq blanks (ssadd blank))
(foreach xx '(-10.0 23.0) (foreach yy '(9.0 54.0) (ssadd (mkbox xx yy 1.0 (+ xx 10.0) (+ yy 10.0) 7.0) blanks)))
(command "_.UNION" blanks "")
(setq body (entlast))
(defun boxcut (x0 y0 z0 x1 y1 z1) (setq cutter (mkbox x0 y0 z0 x1 y1 z1)) (command "_.SUBTRACT" body "" cutter "") (setq body (entlast)))
(boxcut 5.0 -1.0 16.1 16.5 65.0 23.1)
(boxcut 7.75 17.5 -1.0 13.75 65.0 10.0)
(boxcut 7.75 17.5 9.9 13.75 28.5 23.1)
(boxcut 16.5 29.0 16.1 24.0 34.0 23.1)
(boxcut 9.25 -1.0 -1.0 12.25 1.5 23.1)
(boxcut -1.0 -1.0 7.6 24.0 1.5 10.6)
(command "_.VPOINT" (list -1.0 -1.5 1.2))
(command "_.ZOOM" "_Extents")
(princ (strcat "\nBODY_HANDLE=" (cdr (assoc 5 (entget body)))))
(princ (strcat "\nSOLID_COUNT=" (itoa (sslength (ssget "_X" '((0 . "3DSOLID") (410 . "Model")))))))
(princ)
)
