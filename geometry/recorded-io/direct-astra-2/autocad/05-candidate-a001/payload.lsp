(vl-load-com)
(progn
(setvar "CMDECHO" 0)
(setvar "FILEDIA" 0)
(setvar "INSUNITS" 4)
(setq ss (ssget "_X" '((0 . "3DSOLID") (410 . "Model"))))
(setq fp (open "[private value removed]" "w"))
(write-line (strcat "Native 3DSOLIDs in model space: " (itoa (sslength ss))) fp)
(write-line (strcat "Total entities in model space: " (itoa (sslength (ssget "_X" '((410 . "Model")))))) fp)
(write-line "Final source: validated stage03-inspected.a001.dwg, unchanged geometry." fp)
(close fp)
(princ)
)
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
