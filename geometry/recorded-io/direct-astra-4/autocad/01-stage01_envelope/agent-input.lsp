(setvar "CMDECHO" 1)
(setvar "OSMODE" 0)
(setvar "INSUNITS" 4)
(setvar "FACETRES" 10)
(setvar "DELOBJ" 1)
(entmake (list '(0 . "LWPOLYLINE") '(100 . "AcDbEntity") '(100 . "AcDbPolyline") '(90 . 10) '(70 . 1) '(210 0.0 -1.0 0.0) '(10 0 0) '(42 . 0) '(10 44.21 0) '(42 . 0.11175533132835985) '(10 51.5 1.65) '(42 . 0) '(10 51.5 5.56) '(42 . 0.11175533132835985) '(10 44.21 7.21) '(42 . 0) '(10 30.75 7.21) '(42 . -0.41421356237309503) '(10 30 7.96) '(42 . 0) '(10 30 27.5) '(42 . 0) '(10 29.5 28) '(42 . 0) '(10 0 28) '(42 . 0)))
(setq profile (entlast))
(command "_.REVOLVE" profile "" "_non" '(0 0 0) "_non" '(0 0 1) 360)
(setq body (entlast))
(princ (strcat "\nENVELOPE_TYPE=" (cdr (assoc 0 (entget body)))))
(command "_.MASSPROP" body "" "_Yes" "[private value removed]")
(command "_.ZOOM" "_Extents")
(princ "\nENVELOPE_COMPLETE\n")
