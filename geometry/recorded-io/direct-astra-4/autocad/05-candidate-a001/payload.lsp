(vl-load-com)
(setvar "CMDECHO" 1)
(setvar "LOGFILEPATH" "[private value removed]")
(setvar "LOGFILEMODE" 1)
(setvar "OSMODE" 0)
(setvar "INSUNITS" 4)
(setvar "MEASUREMENT" 1)
(setq solids (ssget "_X" '((0 . "3DSOLID") (410 . "Model"))))
(setq modelentities (ssget "_X" '((410 . "Model"))))
(setq body (ssname solids 0))
(command "_.SOLIDEDIT" "_Body" "_Check" body "_eXit" "_eXit")
(command "_.AUDIT" "_Yes")
(command "_.MASSPROP" body "" "_Yes" "[private value removed]")
(setq f (open "[private value removed]" "w"))
(write-line (strcat "Model-space 3DSOLID count: " (itoa (sslength solids))) f)
(write-line (strcat "Model-space entity count: " (itoa (sslength modelentities))) f)
(write-line (strcat "Solid handle: " (cdr (assoc 5 (entget body)))) f)
(write-line (strcat "Command state after ACIS check and audit: " (getvar "CMDNAMES")) f)
(write-line (strcat "Drawing units (4=mm): " (itoa (getvar "INSUNITS"))) f)
(write-line (strcat "Native command log: " (getvar "LOGFILENAME")) f)
(close f)
(setvar "FACETRES" 10)
(setvar "ISOLINES" 4)
(setvar "DISPSILH" 1)
(command "_.UCS" "_World")
(command "_.VPOINT" "_non" '(1 -1 1))
(command "_.ZOOM" "_Extents")
(command "_.VSCURRENT" "_Conceptual")
(princ "\nFINAL_SUBMISSION_VALIDATED\n")
(setvar "LOGFILEMODE" 0)
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
