(vl-load-com)
(setvar "CMDECHO" 0) (setvar "OSMODE" 0) (setvar "DELOBJ" 1) (setvar "INSUNITS" 4) (setvar "SOLIDHIST" 0) (command "_.UCS" "_World")
(defun ck (tag / ss) (setq ss (ssget "_X" '((0 . "3DSOLID")(410 . "Model")))) (if (or (null ss) (/= (sslength ss) 1)) (progn (princ (strcat "\nFAIL_SOLID_COUNT:" tag)) (exit))) (princ (strcat "\nPASS_3DSOLID:" tag " HANDLE=" (cdr (assoc 5 (entget (ssname ss 0)))))) (command "_.MASSPROP" ss "" "_No") (ssname ss 0))
(defun bx (a b h) (command "_.BOX" "_non" a "_non" b h) (entlast))
(defun cyl (a r b) (command "_.CYLINDER" "_non" a r "_Axis" "_non" b) (entlast))
(defun sub1 (body cutter tag) (command "_.SUBTRACT" body "" cutter "") (ck tag))

(setq body (ck "input_mount_holes"))
(foreach x '(2.25 19.75)
 (foreach y '(5 55)
  (setq cutter (cyl (list x y 22.1) 1.25 (list x y 14.1)))
  (setq body (sub1 body cutter "front_M3"))
 ))
(princ)
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
