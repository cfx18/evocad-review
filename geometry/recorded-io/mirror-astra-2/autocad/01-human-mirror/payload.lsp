(vl-load-com)
(setvar "FILEDIA" 0)
(setvar "CMDECHO" 1)
(setvar "OSMODE" 0)
(command "_.UCS" "_World")
(setq mirror-solids (ssget "_X" '((0 . "3DSOLID") (410 . "Model"))))
(if (/= (sslength mirror-solids) 1) (exit))
(command "_.MIRROR3D" mirror-solids "" "_ZX" '(0.0 32.0 0.0) "_Yes")
(setq mirror-final (ssget "_X" '((0 . "3DSOLID") (410 . "Model"))))
(if (/= (sslength mirror-final) 1) (exit))
(princ)
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
