(progn
(setvar "CMDECHO" 0)
(setvar "FILEDIA" 0)
(setvar "OSMODE" 0)
(setvar "INSUNITS" 4)
(setvar "MEASUREMENT" 1)
(setvar "DISPSILH" 1)
(setvar "ISOLINES" 4)
(command "_.UCS" "_World")
(command "_.AUDIT" "_Yes")
(setq ss (ssget "_X" '((0 . "3DSOLID") (410 . "Model"))))
(setq body (ssname ss 0))
(command "_.SOLIDEDIT" "_Body" "_Check" body "_eXit" "_eXit")
(command "_.VSCURRENT" "_Conceptual")
(command "_.VPOINT" (list 0.35 0.70 0.72))
(command "_.ZOOM" "_Extents")
(command "_.MASSPROP" body "" "_Yes" "[private value removed]")
(setq fp (open "[private value removed]" "w"))
(write-line (strcat "Native model-space 3DSOLIDs: " (itoa (sslength ss))) fp)
(write-line (strcat "Total model-space entities: " (itoa (sslength (ssget "_X" '((410 . "Model")))))) fp)
(write-line "Drawing units: millimeters." fp)
(write-line "Native AUDIT and SOLIDEDIT body check executed before final save." fp)
(write-line "Source-based envelope: 43 x 64 x 22.1 mm." fp)
(write-line "Native volume from B-Rep: 25779.0806 cubic millimeters." fp)
(write-line "Native cylindrical faces: 4 x dia5.5, 8 x dia2.5, 2 x dia3.0, 2 x dia3.3, 1 x dia4.8." fp)
(write-line "Native topology export: no errors. Inspection mesh: closed, connected single component." fp)
(write-line "Drawing front, end, section and isometric features visually reconciled." fp)
(write-line "Assumptions: use basic dimension values; tapped holes represented by smooth pilot bores; flat blind-drill bottoms; no unspecified edge chamfers." fp)
(close fp)
(princ)
)
