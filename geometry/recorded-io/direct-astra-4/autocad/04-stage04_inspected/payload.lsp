(vl-load-com)
(setvar "CMDECHO" 1)
(setvar "FACETRES" 10)
(setq solids (ssget "_X" '((0 . "3DSOLID"))))
(command "_.STLOUT" solids "" "_Yes" "[private value removed]")
(command "_.AUDIT" "_Yes")
(princ "\nINSPECTION_EXPORT_COMPLETE\n")
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
