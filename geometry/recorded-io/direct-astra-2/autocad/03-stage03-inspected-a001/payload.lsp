(vl-load-com)
(progn
(setvar "CMDECHO" 0)
(setvar "FILEDIA" 0)
(setvar "FACETRES" 10.0)
(setvar "ISOLINES" 8)
(setq body (ssname (ssget "_X" '((0 . "3DSOLID") (410 . "Model"))) 0))
(command "_.STLOUT" body "" "_Yes" "[private value removed]")
(command "_.VPOINT" (list 1.0 1.5 1.2))
(command "_.ZOOM" "_Extents")
(princ)
)
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
