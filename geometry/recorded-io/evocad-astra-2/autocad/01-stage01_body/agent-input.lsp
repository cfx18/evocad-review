(setvar "CMDECHO" 0)
(setvar "OSMODE" 0)
(setvar "DELOBJ" 1)
(setvar "INSUNITS" 4)
(setvar "SOLIDHIST" 0)
(command "_.UCS" "_World")
(defun ck (tag / ss) (setq ss (ssget "_X" '((0 . "3DSOLID")(410 . "Model")))) (if (or (null ss) (/= (sslength ss) 1)) (progn (princ (strcat "\nFAIL_SOLID_COUNT:" tag)) (exit))) (princ (strcat "\nPASS_3DSOLID:" tag " HANDLE=" (cdr (assoc 5 (entget (ssname ss 0)))))) (command "_.MASSPROP" ss "" "_No") (ssname ss 0))
(defun bx (a b h) (command "_.BOX" "_non" a "_non" b h) (entlast))
(defun sub1 (body cutter tag) (command "_.SUBTRACT" body "" cutter "") (ck tag))

(setq body (bx '(0 0 0) '(23 64 0) 22.1))
(setq ears (ssadd))
(foreach p '((-10 0 1) (23 0 1) (-10 45 1) (23 45 1))
 (setq ear (bx p (list (+ (car p) 10) (+ (cadr p) 10) (caddr p)) 6))
 (ssadd ear ears))
(ssadd body ears)
(command "_.UNION" ears "")
(ck "body_with_four_ears")
(command "_.ZOOM" "_Extents")
(princ)
