(vl-load-com)
(setvar "FILEDIA" 0)
(setvar "CMDECHO" 1)
(setq solids (ssget "_X" '((0 . "3DSOLID"))))
(setq body (ssname solids 0))
(princ (strcat "\nREOPEN_SOLID_COUNT=" (itoa (sslength solids))))
(command "_.SOLIDEDIT" "_Body" "_Check" body)
(repeat 4 (if (> (getvar "CMDACTIVE") 0) (command "_Exit")))
(command "_.SOLIDEDIT" "_Body" "_Separate" body)
(repeat 4 (if (> (getvar "CMDACTIVE") 0) (command "_Exit")))
(setq solids (ssget "_X" '((0 . "3DSOLID"))))
(princ (strcat "\nCONNECTED_COMPONENT_SOLID_COUNT=" (itoa (sslength solids))))
(command "_.MASSPROP" solids "" "_Yes" "[private value removed]")
(princ "\nREOPEN_VERIFY_DONE")
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
