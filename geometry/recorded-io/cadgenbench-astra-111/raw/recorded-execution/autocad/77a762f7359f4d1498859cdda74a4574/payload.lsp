(vl-load-com)
(setvar "FILEDIA" 0)
(setvar "CMDECHO" 1)
(setvar "FACETRES" 10)
(setvar "ISOLINES" 0)
(setq solids (ssget "_X" '((0 . "3DSOLID"))))
(setq body (ssname solids 0))
(princ (strcat "\nFINAL_SOLID_COUNT=" (itoa (sslength solids))))
(command "_.SOLIDEDIT" "_Body" "_Check" body)
(repeat 4 (if (> (getvar "CMDACTIVE") 0) (command "_Exit")))
(command "_.AUDIT" "_Yes")
(command "_.ACISOUT" solids "" "[private value removed]")
(command "_.UCS" "_World")
(command "_.VPOINT" (list 1 -1 1.35))
(command "_.ZOOM" "_Extents")
(princ "\nFINAL_NATIVE_CHECK_AND_EXPORT_COMPLETE")
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
