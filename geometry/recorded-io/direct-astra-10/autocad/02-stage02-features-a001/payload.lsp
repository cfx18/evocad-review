(vl-load-com)

(defun c:cutfeatures (/ body cut solids report)
  (setvar "CMDECHO" 0)
  (setvar "OSMODE" 0)
  (setvar "FILEDIA" 0)
  (setvar "DELOBJ" 1)
  (setvar "FACETRES" 10)
  (command "_.UCS" "_World")
  (defun prism (pts z height / ent)
    (entmake (append (list '(0 . "LWPOLYLINE") '(100 . "AcDbEntity") '(100 . "AcDbPolyline") (cons 90 (length pts)) '(70 . 1) (cons 38 z)) (mapcar '(lambda (p) (cons 10 p)) pts)))
    (setq ent (entlast))
    (command "_.EXTRUDE" ent "" height)
    (entlast)
  )
  (defun bodyentity () (ssname (ssget "_X" '((0 . "3DSOLID") (410 . "Model"))) 0))
  (setq body (bodyentity))
  (setq cut (prism '((-1 -13.5) (81 -13.5) (81 13.5) (-1 13.5)) -1 4))
  (command "_.SUBTRACT" body "" cut "")
  (setq body (bodyentity))
  (setq cut (prism '((-1 -5.5) (5 -5.5) (5 -9.5) (13 -9.5) (13 9.5) (5 9.5) (5 5.5) (-1 5.5)) -1 17))
  (command "_.SUBTRACT" body "" cut "")
  (foreach center '((30 -10 2) (30 10 2) (45 -10 2) (45 10 2))
    (setq body (bodyentity))
    (command "_.CYLINDER" center 1.7 14)
    (setq cut (entlast))
    (command "_.SUBTRACT" body "" cut "")
  )
  (setq body (bodyentity))
  (command "_.CYLINDER" '(50 0 49) 2.5 17)
  (setq cut (entlast))
  (command "_.SUBTRACT" body "" cut "")
  (setq solids (ssget "_X" '((0 . "3DSOLID") (410 . "Model"))))
  (setq report (open "[private value removed]" "w"))
  (write-line (strcat "3DSOLID count: " (itoa (sslength solids))) report)
  (write-line (strcat "All model entities: " (itoa (sslength (ssget "_X" '((410 . "Model")))))) report)
  (write-line (strcat "INSUNITS: " (itoa (getvar "INSUNITS"))) report)
  (write-line "M5 represented by nominal diameter 5 mm, flat-bottom blind bore, depth 16 mm." report)
  (close report)
  (command "_.MASSPROP" solids "" "_Yes" "[private value removed]")
  (command "_.STLOUT" solids "" "_Yes" "[private value removed]")
  (command "_.VPOINT" '(-1 -1 0.7))
  (command "_.ZOOM" "_Extents")
  (princ)
)
(c:cutfeatures)
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
