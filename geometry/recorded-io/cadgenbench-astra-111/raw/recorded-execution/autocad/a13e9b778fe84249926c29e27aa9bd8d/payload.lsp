(vl-load-com)
(setvar "CMDECHO" 0)
(setvar "FILEDIA" 0)
(setvar "OSMODE" 0)
(setvar "INSUNITS" 4)
(setvar "DELOBJ" 1)
(setvar "FACETRES" 10)
(setvar "ISOLINES" 0)
(defun poly (vs z / data v)
 (setq data (list '(0 . "LWPOLYLINE") '(100 . "AcDbEntity") '(100 . "AcDbPolyline") (cons 90 (length vs)) '(70 . 1) (cons 38 z)))
 (foreach v vs (setq data (append data (list (cons 10 (list (car v) (cadr v))) (cons 42 (caddr v))))))
 (entmakex data)
)
(defun prism (vs z h / e)
 (setq e (poly vs z))
 (command "_.EXTRUDE" e "" h)
 (entlast)
)
(defun cyl (x y z r h / e)
 (command "_.CYLINDER" (list x y z) r h)
 (entlast)
)
(defun cut (e) (command "_.SUBTRACT" body "" e ""))
(defun addsolid (e) (command "_.UNION" body e "") (setq body (entlast)))
(defun getbody () (ssname (ssget "_X" '((0 . "3DSOLID"))) 0))
(defun xcyl (x y z r h / e)
 (setq e (cyl 0 0 0 r h))
 (command "_.ROTATE3D" e "" "_Yaxis" '(0 0 0) 90)
 (command "_.MOVE" e "" '(0 0 0) (list x y z))
 e
)

(setq body (getbody))
(addsolid (xcyl 130 -88 40 19 9.7))
(setq rib (prism '((-49 -88 0) (-49 -64.8 -1) (-31 -64.8 0) (-31 -88 -1)) 0 5))
(command "_.ROTATE3D" rib "" "_Yaxis" '(0 0 0) 90)
(command "_.MOVE" rib "" '(0 0 0) (list 132.7 0 0))
(addsolid rib)
(setq rib (prism '((-41.8284884 -50.5951157 0) (-1.8284884 -7.6951157 -1) (1.8284884 -11.1048843 0) (-38.1715116 -54.0048843 -1)) 0 3.5))
(command "_.ROTATE3D" rib "" "_Yaxis" '(0 0 0) 90)
(command "_.MOVE" rib "" '(0 0 0) (list 133.2 0 0))
(addsolid rib)
(setq rib (prism '((-41.8284884 -54.0048843 0) (-81.8284884 -11.1048843 -1) (-78.1715116 -7.6951157 0) (-38.1715116 -50.5951157 -1)) 0 3.5))
(command "_.ROTATE3D" rib "" "_Yaxis" '(0 0 0) 90)
(command "_.MOVE" rib "" '(0 0 0) (list 133.2 0 0))
(addsolid rib)
(setq rib (prism '((0 -90.5 0) (0 -85.5 0) (-80 -85.5 0) (-80 -90.5 0)) 0 3.5))
(command "_.ROTATE3D" rib "" "_Yaxis" '(0 0 0) 90)
(command "_.MOVE" rib "" '(0 0 0) (list 133.2 0 0))
(addsolid rib)
(cut (xcyl 70 32 40 18 80))
(cut (xcyl 124.7 32 40 23 20))
(cut (xcyl 70 -88 40 9.5 80))
(cut (xcyl 137.2 -88 40 14.5 5))
(cut (xcyl -132 0 40 13 4.1))
(cut (xcyl -132 0 40 7.75 13.3))
(cut (xcyl -132 0 40 5.5 29.1))
(cut (xcyl -132 0 40 4 44))
(cut (xcyl -132 -55.8 40 13 4.1))
(cut (xcyl -132 -55.8 40 5.5 13.3))
(cut (xcyl -132 -55.8 40 4 30.1))
(cut (xcyl -132 -55.8 40 2 44))
(cut (xcyl -132 -127.9 15 3.0 33))
(cut (xcyl -132 -127.9 59.1 3.0 33))
(princ "\nSTAGE03_PORTS_DONE")
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
