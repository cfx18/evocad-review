(progn
(setvar "CMDECHO" 0)
(setvar "OSMODE" 0)
(setvar "FILEDIA" 0)
(command "_.UCS" "_World")
(setq body (ssname (ssget "_X" '((0 . "3DSOLID") (410 . "Model"))) 0))
(defun bore (p0 p1 radius) (command "_.CYLINDER" p0 radius "_Axis" p1) (setq cutter (entlast)) (command "_.SUBTRACT" body "" cutter "") (setq body (entlast)))
(foreach xx '(-5.0 28.0) (foreach yy '(14.0 59.0) (bore (list xx yy 0.0) (list xx yy 8.0) 2.75)))
(foreach xx '(2.25 19.75) (foreach yy '(9.0 59.0) (bore (list xx yy 23.1) (list xx yy 14.1) 1.25)))
(foreach xx '(3.5 19.5) (foreach zz '(5.6 13.1) (bore (list xx -1.0 zz) (list xx 8.0 zz) 1.25)))
(bore (list -1.0 34.5 5.1) (list 24.0 34.5 5.1) 1.5)
(bore (list -1.0 38.5 5.1) (list 9.25 38.5 5.1) 1.65)
(bore (list 24.0 38.5 5.1) (list 13.75 38.5 5.1) 1.65)
(bore (list 10.75 40.5 9.9) (list 10.75 40.5 12.0) 2.4)
(command "_.SOLIDEDIT" "_Body" "_Check" body "_eXit" "_eXit")
(command "_.MASSPROP" body "" "_Yes" "[private value removed]")
(command "_.VPOINT" (list -1.0 -1.5 1.2))
(command "_.ZOOM" "_Extents")
(setq fp (open "[private value removed]" "w"))
(write-line (strcat "Model-space 3DSOLID count: " (itoa (sslength (ssget "_X" '((0 . "3DSOLID") (410 . "Model")))))) fp)
(write-line (strcat "All model-space entities: " (itoa (sslength (ssget "_X" '((410 . "Model")))))) fp)
(write-line (strcat "Solid handle: " (cdr (assoc 5 (entget body)))) fp)
(write-line "Units: millimeters. Bores use smooth specified pilot/drill diameters; no helical threads." fp)
(close fp)
(princ)
)
