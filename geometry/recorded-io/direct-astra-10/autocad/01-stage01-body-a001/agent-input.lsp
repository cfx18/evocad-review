(defun c:buildbody (/ base top web solids)
  (setvar "CMDECHO" 0)
  (setvar "OSMODE" 0)
  (setvar "INSUNITS" 4)
  (setvar "LUNITS" 2)
  (setvar "LUPREC" 6)
  (setvar "DELOBJ" 1)
  (setvar "SOLIDHIST" 1)
  (command "_.UCS" "_World")
  (defun prism (pts z height / ent)
    (entmake (append (list '(0 . "LWPOLYLINE") '(100 . "AcDbEntity") '(100 . "AcDbPolyline") (cons 90 (length pts)) '(70 . 1) (cons 38 z)) (mapcar '(lambda (p) (cons 10 p)) pts)))
    (setq ent (entlast))
    (command "_.EXTRUDE" ent "" height)
    (if (/= (cdr (assoc 0 (entget (entlast)))) "3DSOLID") (progn (princ "\nPRISM_FAILED") (exit)))
    (entlast)
  )
  (setq base (prism '((0 -12) (3 -15) (77 -15) (80 -12) (80 12) (77 15) (3 15) (0 12)) 0 15))
  (setq top (prism '((30 -12) (33 -15) (77 -15) (80 -12) (80 12) (77 15) (33 15) (30 12)) 53 12))
  (setq web (prism '((30 -5) (80 -5) (80 5) (30 5)) 15 38))
  (command "_.UNION" base top web "")
  (setq solids (ssget "_X" '((0 . "3DSOLID") (410 . "Model"))))
  (princ (strcat "\nBODY_SOLID_COUNT=" (itoa (sslength solids))))
  (command "_.MASSPROP" solids "" "_No")
  (command "_.VPOINT" '(-1 -1 0.7))
  (command "_.ZOOM" "_Extents")
  (princ)
)
(c:buildbody)
