(vl-load-com)
(setvar "CMDECHO" 1)
(setvar "OSMODE" 0)
(setvar "DELOBJ" 1)
(setq body (ssname (ssget "_X" '((0 . "3DSOLID"))) 0))
(entmake (list '(0 . "LWPOLYLINE") '(100 . "AcDbEntity") '(100 . "AcDbPolyline") '(90 . 144) '(70 . 1) '(38 . -1.0) '(10 -3.8057876977 46.5621061511) '(42 . 0.618033988750) '(10 3.8057876977 46.5621061511) '(42 . 0.000000000000) '(10 5.9992814587 50.9490936732) '(42 . -0.317537618929) '(10 6.3043338911 51.1126733227) '(42 . -0.004088837118) '(10 7.1394143790 51.0027328907) '(42 . -0.317537618929) '(10 7.3917348732 50.7657737034) '(42 . 0.000000000000) '(10 8.3750512254 45.9605511956) '(42 . 0.618033988750) '(10 15.7272684786 43.9905305200) '(42 . 0.000000000000) '(10 18.9814566735 47.6603171065) '(42 . -0.317537618929) '(10 19.3184522250 47.7393695353) '(42 . -0.004088837118) '(10 20.0966233577 47.4170404983) '(42 . -0.317537618929) '(10 20.2790166889 47.1228501502) '(42 . 0.000000000000) '(10 19.9851442480 42.2268606295) '(42 . 0.618033988750) '(10 26.5769619032 38.4210729317) '(42 . 0.000000000000) '(10 30.6700769843 41.1235686914) '(42 . -0.317537618929) '(10 31.0160499650 41.1127066072) '(42 . -0.004088837118) '(10 31.6842806657 40.5999551563) '(42 . -0.317537618929) '(10 31.7843170299 40.2685822334) '(42 . 0.000000000000) '(10 30.2332827170 35.6154792946) '(42 . 0.618033988750) '(10 35.6154792946 30.2332827170) '(42 . 0.000000000000) '(10 40.2685822334 31.7843170299) '(42 . -0.317537618929) '(10 40.5999551563 31.6842806657) '(42 . -0.004088837118) '(10 41.1127066072 31.0160499650) '(42 . -0.317537618929) '(10 41.1235686914 30.6700769843) '(42 . 0.000000000000) '(10 38.4210729317 26.5769619032) '(42 . 0.618033988750) '(10 42.2268606295 19.9851442480) '(42 . 0.000000000000) '(10 47.1228501502 20.2790166889) '(42 . -0.317537618929) '(10 47.4170404983 20.0966233577) '(42 . -0.004088837118) '(10 47.7393695353 19.3184522250) '(42 . -0.317537618929) '(10 47.6603171065 18.9814566735) '(42 . 0.000000000000) '(10 43.9905305200 15.7272684786) '(42 . 0.618033988750) '(10 45.9605511956 8.3750512254) '(42 . 0.000000000000) '(10 50.7657737034 7.3917348732) '(42 . -0.317537618929) '(10 51.0027328907 7.1394143790) '(42 . -0.004088837118) '(10 51.1126733227 6.3043338911) '(42 . -0.317537618929) '(10 50.9490936732 5.9992814587) '(42 . 0.000000000000) '(10 46.5621061511 3.8057876977) '(42 . 0.618033988750) '(10 46.5621061511 -3.8057876977) '(42 . 0.000000000000) '(10 50.9490936732 -5.9992814587) '(42 . -0.317537618929) '(10 51.1126733227 -6.3043338911) '(42 . -0.004088837118) '(10 51.0027328907 -7.1394143790) '(42 . -0.317537618929) '(10 50.7657737034 -7.3917348732) '(42 . 0.000000000000) '(10 45.9605511956 -8.3750512254) '(42 . 0.618033988750) '(10 43.9905305200 -15.7272684786) '(42 . 0.000000000000) '(10 47.6603171065 -18.9814566735) '(42 . -0.317537618929) '(10 47.7393695353 -19.3184522250) '(42 . -0.004088837118) '(10 47.4170404983 -20.0966233577) '(42 . -0.317537618929) '(10 47.1228501502 -20.2790166889) '(42 . 0.000000000000) '(10 42.2268606295 -19.9851442480) '(42 . 0.618033988750) '(10 38.4210729317 -26.5769619032) '(42 . 0.000000000000) '(10 41.1235686914 -30.6700769843) '(42 . -0.317537618929) '(10 41.1127066072 -31.0160499650) '(42 . -0.004088837118) '(10 40.5999551563 -31.6842806657) '(42 . -0.317537618929) '(10 40.2685822334 -31.7843170299) '(42 . 0.000000000000) '(10 35.6154792946 -30.2332827170) '(42 . 0.618033988750) '(10 30.2332827170 -35.6154792946) '(42 . 0.000000000000) '(10 31.7843170299 -40.2685822334) '(42 . -0.317537618929) '(10 31.6842806657 -40.5999551563) '(42 . -0.004088837118) '(10 31.0160499650 -41.1127066072) '(42 . -0.317537618929) '(10 30.6700769843 -41.1235686914) '(42 . 0.000000000000) '(10 26.5769619032 -38.4210729317) '(42 . 0.618033988750) '(10 19.9851442480 -42.2268606295) '(42 . 0.000000000000) '(10 20.2790166889 -47.1228501502) '(42 . -0.317537618929) '(10 20.0966233577 -47.4170404983) '(42 . -0.004088837118) '(10 19.3184522250 -47.7393695353) '(42 . -0.317537618929) '(10 18.9814566735 -47.6603171065) '(42 . 0.000000000000) '(10 15.7272684786 -43.9905305200) '(42 . 0.618033988750) '(10 8.3750512254 -45.9605511956) '(42 . 0.000000000000) '(10 7.3917348732 -50.7657737034) '(42 . -0.317537618929) '(10 7.1394143790 -51.0027328907) '(42 . -0.004088837118) '(10 6.3043338911 -51.1126733227) '(42 . -0.317537618929) '(10 5.9992814587 -50.9490936732) '(42 . 0.000000000000) '(10 3.8057876977 -46.5621061511) '(42 . 0.618033988750) '(10 -3.8057876977 -46.5621061511) '(42 . 0.000000000000) '(10 -5.9992814587 -50.9490936732) '(42 . -0.317537618929) '(10 -6.3043338911 -51.1126733227) '(42 . -0.004088837118) '(10 -7.1394143790 -51.0027328907) '(42 . -0.317537618929) '(10 -7.3917348732 -50.7657737034) '(42 . 0.000000000000) '(10 -8.3750512254 -45.9605511956) '(42 . 0.618033988750) '(10 -15.7272684786 -43.9905305200) '(42 . 0.000000000000) '(10 -18.9814566735 -47.6603171065) '(42 . -0.317537618929) '(10 -19.3184522250 -47.7393695353) '(42 . -0.004088837118) '(10 -20.0966233577 -47.4170404983) '(42 . -0.317537618929) '(10 -20.2790166889 -47.1228501502) '(42 . 0.000000000000) '(10 -19.9851442480 -42.2268606295) '(42 . 0.618033988750) '(10 -26.5769619032 -38.4210729317) '(42 . 0.000000000000) '(10 -30.6700769843 -41.1235686914) '(42 . -0.317537618929) '(10 -31.0160499650 -41.1127066072) '(42 . -0.004088837118) '(10 -31.6842806657 -40.5999551563) '(42 . -0.317537618929) '(10 -31.7843170299 -40.2685822334) '(42 . 0.000000000000) '(10 -30.2332827170 -35.6154792946) '(42 . 0.618033988750) '(10 -35.6154792946 -30.2332827170) '(42 . 0.000000000000) '(10 -40.2685822334 -31.7843170299) '(42 . -0.317537618929) '(10 -40.5999551563 -31.6842806657) '(42 . -0.004088837118) '(10 -41.1127066072 -31.0160499650) '(42 . -0.317537618929) '(10 -41.1235686914 -30.6700769843) '(42 . 0.000000000000) '(10 -38.4210729317 -26.5769619032) '(42 . 0.618033988750) '(10 -42.2268606295 -19.9851442480) '(42 . 0.000000000000) '(10 -47.1228501502 -20.2790166889) '(42 . -0.317537618929) '(10 -47.4170404983 -20.0966233577) '(42 . -0.004088837118) '(10 -47.7393695353 -19.3184522250) '(42 . -0.317537618929) '(10 -47.6603171065 -18.9814566735) '(42 . 0.000000000000) '(10 -43.9905305200 -15.7272684786) '(42 . 0.618033988750) '(10 -45.9605511956 -8.3750512254) '(42 . 0.000000000000) '(10 -50.7657737034 -7.3917348732) '(42 . -0.317537618929) '(10 -51.0027328907 -7.1394143790) '(42 . -0.004088837118) '(10 -51.1126733227 -6.3043338911) '(42 . -0.317537618929) '(10 -50.9490936732 -5.9992814587) '(42 . 0.000000000000) '(10 -46.5621061511 -3.8057876977) '(42 . 0.618033988750) '(10 -46.5621061511 3.8057876977) '(42 . 0.000000000000) '(10 -50.9490936732 5.9992814587) '(42 . -0.317537618929) '(10 -51.1126733227 6.3043338911) '(42 . -0.004088837118) '(10 -51.0027328907 7.1394143790) '(42 . -0.317537618929) '(10 -50.7657737034 7.3917348732) '(42 . 0.000000000000) '(10 -45.9605511956 8.3750512254) '(42 . 0.618033988750) '(10 -43.9905305200 15.7272684786) '(42 . 0.000000000000) '(10 -47.6603171065 18.9814566735) '(42 . -0.317537618929) '(10 -47.7393695353 19.3184522250) '(42 . -0.004088837118) '(10 -47.4170404983 20.0966233577) '(42 . -0.317537618929) '(10 -47.1228501502 20.2790166889) '(42 . 0.000000000000) '(10 -42.2268606295 19.9851442480) '(42 . 0.618033988750) '(10 -38.4210729317 26.5769619032) '(42 . 0.000000000000) '(10 -41.1235686914 30.6700769843) '(42 . -0.317537618929) '(10 -41.1127066072 31.0160499650) '(42 . -0.004088837118) '(10 -40.5999551563 31.6842806657) '(42 . -0.317537618929) '(10 -40.2685822334 31.7843170299) '(42 . 0.000000000000) '(10 -35.6154792946 30.2332827170) '(42 . 0.618033988750) '(10 -30.2332827170 35.6154792946) '(42 . 0.000000000000) '(10 -31.7843170299 40.2685822334) '(42 . -0.317537618929) '(10 -31.6842806657 40.5999551563) '(42 . -0.004088837118) '(10 -31.0160499650 41.1127066072) '(42 . -0.317537618929) '(10 -30.6700769843 41.1235686914) '(42 . 0.000000000000) '(10 -26.5769619032 38.4210729317) '(42 . 0.618033988750) '(10 -19.9851442480 42.2268606295) '(42 . 0.000000000000) '(10 -20.2790166889 47.1228501502) '(42 . -0.317537618929) '(10 -20.0966233577 47.4170404983) '(42 . -0.004088837118) '(10 -19.3184522250 47.7393695353) '(42 . -0.317537618929) '(10 -18.9814566735 47.6603171065) '(42 . 0.000000000000) '(10 -15.7272684786 43.9905305200) '(42 . 0.618033988750) '(10 -8.3750512254 45.9605511956) '(42 . 0.000000000000) '(10 -7.3917348732 50.7657737034) '(42 . -0.317537618929) '(10 -7.1394143790 51.0027328907) '(42 . -0.004088837118) '(10 -6.3043338911 51.1126733227) '(42 . -0.317537618929) '(10 -5.9992814587 50.9490936732) '(42 . 0.000000000000)))
(setq toothprofile (entlast))
(command "_.EXTRUDE" toothprofile "" 30)
(setq toothprism (entlast))
(princ (strcat "\nTOOTH_PRISM_TYPE=" (cdr (assoc 0 (entget toothprism)))))
(command "_.INTERSECT" body toothprism "")
(setq finalbody (ssname (ssget "_X" '((0 . "3DSOLID"))) 0))
(command "_.MASSPROP" finalbody "" "_Yes" "[private value removed]")
(command "_.AUDIT" "_Yes")
(princ (strcat "\nSOLID_COUNT=" (itoa (sslength (ssget "_X" '((0 . "3DSOLID")))))))
(setvar "FACETRES" 10)
(setvar "ISOLINES" 4)
(command "_.VPOINT" "_non" '(1 -1 1))
(command "_.ZOOM" "_Extents")
(princ "\nTOOTH_PROFILE_COMPLETE\n")
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
