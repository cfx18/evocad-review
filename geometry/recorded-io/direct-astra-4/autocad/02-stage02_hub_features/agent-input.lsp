(setvar "CMDECHO" 1)
(setvar "OSMODE" 0)
(setvar "DELOBJ" 1)
(setq body (ssname (ssget "_X" '((0 . "3DSOLID"))) 0))
(entmake (list '(0 . "LWPOLYLINE") '(100 . "AcDbEntity") '(100 . "AcDbPolyline") '(90 . 8) '(70 . 1) '(210 0.0 -1.0 0.0) '(10 0 -1) '(42 . 0) '(10 16 -1) '(42 . 0) '(10 16 0) '(42 . 0) '(10 15 1) '(42 . 0) '(10 15 27) '(42 . 0) '(10 16 28) '(42 . 0) '(10 16 29) '(42 . 0) '(10 0 29) '(42 . 0)))
(command "_.REVOLVE" (entlast) "" "_non" '(0 0 0) "_non" '(0 0 1) 360)
(setq bore (entlast))
(command "_.SUBTRACT" body "" bore "")
(command "_.BOX" "_non" '(-4 0 -1) "_non" '(4 18.3 -1) 30)
(setq keyway (entlast))
(command "_.SUBTRACT" body "" keyway "")
(command "_.CYLINDER" "_non" '(0 -35 20) 3 "_Axis" "_non" '(0 35 20))
(setq crosshole (entlast))
(princ (strcat "\nCROSSHOLE_TYPE=" (cdr (assoc 0 (entget crosshole)))))
(command "_.SUBTRACT" body "" crosshole "")
(command "_.MASSPROP" body "" "_Yes" "[private value removed]")
(princ (strcat "\nSOLID_COUNT=" (itoa (sslength (ssget "_X" '((0 . "3DSOLID")))))))
(princ "\nBORE_KEYWAY_HOLES_COMPLETE\n")
