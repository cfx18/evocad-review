(vl-load-com)
(setvar "CMDECHO" 0)
(setvar "FILEDIA" 0)
(setvar "OSMODE" 0)
(setvar "INSUNITS" 4)
(setvar "DELOBJ" 1)
(setvar "FACETRES" 10)
(setvar "ISOLINES" 0)
(defun poly (vs z / data v)
 (setq data (list '(0 . "LWPOLYLINE") '(100 . "AcDbEntity") '(100 . "AcDbPolyline") (cons 90 (length vs)) '(70 . 1) (cons 38 z)))
 (foreach v vs (setq data (append data (list (cons 10 (list (car v) (cadr v))) (cons 42 (caddr v))))))
 (entmakex data)
)
(defun prism (vs z h / e)
 (setq e (poly vs z))
 (command "_.EXTRUDE" e "" h)
 (entlast)
)
(defun cyl (x y z r h / e)
 (command "_.CYLINDER" (list x y z) r h)
 (entlast)
)
(defun cut (e) (command "_.SUBTRACT" body "" e ""))
(defun addsolid (e) (command "_.UNION" body e "") (setq body (entlast)))
(defun getbody () (ssname (ssget "_X" '((0 . "3DSOLID"))) 0))
(defun xcyl (x y z r h / e)
 (setq e (cyl 0 0 0 r h))
 (command "_.ROTATE3D" e "" "_Yaxis" '(0 0 0) 90)
 (command "_.MOVE" e "" '(0 0 0) (list x y z))
 e
)

(setq body (prism '((153.7 132.5 0) (129.7 132.5 -0.0330112) (121 128.2 0) (52 120 -0.2750539) (40.0795042 123.3520302 0.2820292) (-91.7117495 91.7117495 -0.4549736) (-131 96 -0.2267891) (-132.9 102.95 0.2920457) (-134.2 120.1 -0.1689489) (-135 124 0) (-135 132.5 0) (-158.5 132.5 0) (-158.5 124 -0.1687389) (-160 119.8 0.3616816) (-158.5 99.3 0) (-158.5 93 0.2521176) (-153 84 0) (-130.6433087 61.6433087 -0.2750281) (-124.3518479 36.8606554 0.0721677) (-129.7 0 0) (-129.7 -55.8 0.0890449) (-118 -111 0) (-118 -143 0.4142136) (-110 -152.9 0) (-71.5 -191.4 0.2211811) (-68 -192.9 0) (68 -192.9 0.2211811) (71.5 -191.4 0) (110 -152.9 0.1698243) (122 -122 0) (134.7 -105 0) (134.7 105 -0.5293802) (145 117 0) (149.5 117 0) (153.7 125 0)) 0 80))
(cut (prism '((92 0 1) (-92 0 0) (-92 -55.8 1) (92 -55.8 0)) -1 82))
(princ "\nSTAGE01_BODY_DONE")


(setvar "CMDECHO" 0)
(setvar "FILEDIA" 0)
(setvar "OSMODE" 0)
(setvar "INSUNITS" 4)
(setvar "DELOBJ" 1)
(setvar "FACETRES" 10)
(setvar "ISOLINES" 0)
(defun poly (vs z / data v)
 (setq data (list '(0 . "LWPOLYLINE") '(100 . "AcDbEntity") '(100 . "AcDbPolyline") (cons 90 (length vs)) '(70 . 1) (cons 38 z)))
 (foreach v vs (setq data (append data (list (cons 10 (list (car v) (cadr v))) (cons 42 (caddr v))))))
 (entmakex data)
)
(defun prism (vs z h / e)
 (setq e (poly vs z))
 (command "_.EXTRUDE" e "" h)
 (entlast)
)
(defun cyl (x y z r h / e)
 (command "_.CYLINDER" (list x y z) r h)
 (entlast)
)
(defun cut (e) (command "_.SUBTRACT" body "" e ""))
(defun addsolid (e) (command "_.UNION" body e "") (setq body (entlast)))
(defun getbody () (ssname (ssget "_X" '((0 . "3DSOLID"))) 0))
(defun xcyl (x y z r h / e)
 (setq e (cyl 0 0 0 r h))
 (command "_.ROTATE3D" e "" "_Yaxis" '(0 0 0) 90)
 (command "_.MOVE" e "" '(0 0 0) (list x y z))
 e
)

(setq body (getbody))
(setq cutters (ssadd))
(ssadd (cyl 111.6 0 -1 6.5 82) cutters)
(ssadd (cyl 111.6 -55.8 -1 6.5 82) cutters)
(ssadd (cyl 83.8410773 73.6561861 -1 6.5 82) cutters)
(ssadd (cyl 83.8410773 -129.4561861 -1 6.5 82) cutters)
(ssadd (cyl 35.7804097 105.708667 -1 6.5 82) cutters)
(ssadd (cyl 35.7804097 -161.508667 -1 6.5 82) cutters)
(ssadd (cyl -21.8675897 109.4365959 -1 6.5 82) cutters)
(ssadd (cyl -21.8675897 -165.2365959 -1 6.5 82) cutters)
(ssadd (cyl -57.9783329 95.3576054 -1 6.5 82) cutters)
(ssadd (cyl -57.9783329 -151.1576054 -1 6.5 82) cutters)
(ssadd (cyl -87.0960335 69.7770804 -1 6.5 82) cutters)
(ssadd (cyl -87.0960335 -125.5770804 -1 6.5 82) cutters)
(ssadd (cyl -105.708667 35.7804097 -1 6.5 82) cutters)
(ssadd (cyl -105.708667 -91.5804097 -1 6.5 82) cutters)
(ssadd (cyl -111.6 -27.9 -1 6.5 82) cutters)
(ssadd (cyl -147 110.5 -1 11 82) cutters)
(ssadd (prism '((104.8 120.5 0) (118.4 120.5 -1) (118.4 100.5 0) (104.8 100.5 -1)) -1 82) cutters)
(ssadd (prism '((-143.5 89.7 0.9390415) (-147 80.8 0) (-122.4 61.9 1.0045311) (-112.4 79.4 0) (-138.2 89 0.1979401)) -1 82) cutters)
(ssadd (prism '((99.8501429 12.2600559 0.1196853) (83.1054884 56.6907205 -1) (87.8968585 59.9591716 -0.1196853) (105.6069105 12.9668981 -1)) -1 82) cutters)
(ssadd (prism '((83.1054884 -112.4907205 0.1196853) (99.8501429 -68.0600559 -1) (105.6069105 -68.7668981 -0.1196853) (87.8968585 -115.7591716 -1)) -1 82) cutters)
(ssadd (prism '((66.9221737 75.1118011 0.0699268) (43.6261039 90.6483483 -1) (46.1413266 95.8745951 -0.0699268) (70.7805097 79.4423026 -1)) -1 82) cutters)
(ssadd (prism '((43.6261039 -146.4483483 0.0699268) (66.9221737 -130.9118011 -1) (70.7805097 -135.2423026 -0.0699268) (46.1413266 -151.6745951 -1)) -1 82) cutters)
(ssadd (prism '((20.4004019 98.5098147 0.0699268) (-7.5428599 100.3168244 -1) (-7.9777365 106.1004982 -0.0699268) (21.5765682 104.1893071 -1)) -1 82) cutters)
(ssadd (prism '((-7.5428599 -156.1168244 0.0699268) (20.4004019 -154.3098147 -1) (21.5765682 -159.9893071 -0.0699268) (-7.9777365 -161.9004982 -1)) -1 82) cutters)
(ssadd (prism '((-31.5876411 95.5122031 0.0261859) (-41.3983445 91.6871696 -1) (-43.7851278 96.9733086 -0.0261859) (-33.4087973 101.0188708 -1)) -1 82) cutters)
(ssadd (prism '((-41.3983445 -147.4871696 0.0261859) (-31.5876411 -151.3122031 -1) (-33.4087973 -156.8188708 -0.0261859) (-43.7851278 -152.7733086 -1)) -1 82) cutters)
(ssadd (prism '((-62.3497706 78.9485029 0.0261859) (-70.2605777 71.998689 -1) (-74.3113864 76.1497069 -0.0261859) (-65.944489 83.5002058 -1)) -1 82) cutters)
(ssadd (prism '((-70.2605777 -127.798689 0.0261859) (-62.3497706 -134.7485029 -1) (-65.944489 -139.3002058 -0.0261859) (-74.3113864 -131.9497069 -1)) -1 82) cutters)
(ssadd (prism '((-85.5915976 52.8624481 0.0261859) (-90.6483483 43.6261039 -1) (-95.8745951 46.1413266 -0.0261859) (-90.526302 55.9101837 -1)) -1 82) cutters)
(ssadd (prism '((-90.6483483 -99.4261039 0.0261859) (-85.5915976 -108.6624481 -1) (-90.526302 -111.7101837 -0.0261859) (-95.8745951 -101.9413266 -1)) -1 82) cutters)
(ssadd (prism '((-98.5098147 20.4004019 0.0510953) (-100.6 0 0) (-100.6 -16.6 -1) (-106.4 -16.6 0) (-106.4 0 -0.0510953) (-104.1893071 21.5765682 -1)) -1 82) cutters)
(ssadd (prism '((-98.5098147 -76.2004019 -0.0510953) (-100.6 -55.8 0) (-100.6 -39.2 1) (-106.4 -39.2 0) (-106.4 -55.8 0.0510953) (-104.1893071 -77.3765682 1)) -1 82) cutters)
(ssadd (prism '((106.4 -12 0) (106.4 -43.8 -1) (100.6 -43.8 0) (100.6 -12 -1)) -1 82) cutters)
(ssadd (prism '((114.7383351 14.0880961 0.1196853) (95.4969628 65.1436113 -1) (100.288333 68.4120623 -0.1196853) (120.4951028 14.7949383 -1)) -1 82) cutters)
(ssadd (prism '((95.4969628 -120.9436113 0.1196853) (114.7383351 -69.8880961 -1) (120.4951028 -70.5949383 -0.1196853) (100.288333 -124.2120623 -1)) -1 82) cutters)
(ssadd (prism '((76.900629 86.3113739 0.0699268) (50.1309902 104.1645037 -1) (52.6462129 109.3907504 -0.0699268) (80.7589651 90.6418753 -1)) -1 82) cutters)
(ssadd (prism '((50.1309902 -159.9645037 0.0699268) (76.900629 -142.1113739 -1) (80.7589651 -146.4418753 -0.0699268) (52.6462129 -165.1907504 -1)) -1 82) cutters)
(ssadd (prism '((23.4422113 113.1981569 0.0699268) (-8.6675408 115.2746014 -1) (-9.1024174 121.0582752 -0.0699268) (24.6183777 118.8776492 -1)) -1 82) cutters)
(ssadd (prism '((-8.6675408 -171.0746014 0.0699268) (23.4422113 -168.9981569 -1) (24.6183777 -174.6776492 -0.0699268) (-9.1024174 -176.8582752 -1)) -1 82) cutters)
(ssadd (prism '((-36.2975279 109.7535852 0.0261859) (-47.5710599 105.3582188 -1) (-49.9578431 110.6443578 -0.0261859) (-38.1186842 115.260253 -1)) -1 82) cutters)
(ssadd (prism '((-47.5710599 -161.1582188 0.0261859) (-36.2975279 -165.5535852 -1) (-38.1186842 -171.060253 -0.0261859) (-49.9578431 -166.4443578 -1)) -1 82) cutters)
(ssadd (prism '((-71.6464561 90.7201484 0.0261859) (-80.736807 82.73408 -1) (-84.7876157 86.8850979 -0.0261859) (-75.2411745 95.2718514 -1)) -1 82) cutters)
(ssadd (prism '((-80.736807 -138.53408 0.0261859) (-71.6464561 -146.5201484 -1) (-75.2411745 -151.0718514 -0.0261859) (-84.7876157 -142.6850979 -1)) -1 82) cutters)
(ssadd (prism '((-98.3537642 60.7445229 0.0261859) (-104.1645037 50.1309902 -1) (-109.3907504 52.6462129 -0.0261859) (-103.2884687 63.7922584 -1)) -1 82) cutters)
(ssadd (prism '((-104.1645037 -105.9309902 0.0261859) (-98.3537642 -116.5445229 -1) (-103.2884687 -119.5922584 -0.0261859) (-109.3907504 -108.4462129 -1)) -1 82) cutters)
(ssadd (prism '((-113.1981569 23.4422113 0.0510953) (-115.6 0 0) (-115.6 -16.6 -1) (-121.4 -16.6 0) (-121.4 0 -0.0510953) (-118.8776492 24.6183777 -1)) -1 82) cutters)
(ssadd (prism '((-113.1981569 -79.2422113 -0.0510953) (-115.6 -55.8 0) (-115.6 -39.2 1) (-121.4 -39.2 0) (-121.4 -55.8 0.0510953) (-118.8776492 -80.4183777 1)) -1 82) cutters)
(ssadd (prism '((121.4 -12 0) (121.4 -43.8 -1) (115.6 -43.8 0) (115.6 -12 -1)) -1 82) cutters)
(ssadd (prism '((50.463156 -178.1064391 0.1898559) (97.8342834 -146.7521738 -1) (104.3874998 -151.3407853 -0.1898559) (52.1264496 -185.9316199 -1)) -1 82) cutters)
(ssadd (prism '((-97.8342834 -146.7521738 0.1898559) (-50.463156 -178.1064391 -1) (-52.1264496 -185.9316199 -0.1898559) (-104.3874998 -151.3407853 -1)) -1 82) cutters)
(command "_.SUBTRACT" body "" cutters "")
(princ "\nSTAGE02_THROUGH_FEATURES_DONE")


(setvar "CMDECHO" 0)
(setvar "FILEDIA" 0)
(setvar "OSMODE" 0)
(setvar "INSUNITS" 4)
(setvar "DELOBJ" 1)
(setvar "FACETRES" 10)
(setvar "ISOLINES" 0)
(defun poly (vs z / data v)
 (setq data (list '(0 . "LWPOLYLINE") '(100 . "AcDbEntity") '(100 . "AcDbPolyline") (cons 90 (length vs)) '(70 . 1) (cons 38 z)))
 (foreach v vs (setq data (append data (list (cons 10 (list (car v) (cadr v))) (cons 42 (caddr v))))))
 (entmakex data)
)
(defun prism (vs z h / e)
 (setq e (poly vs z))
 (command "_.EXTRUDE" e "" h)
 (entlast)
)
(defun cyl (x y z r h / e)
 (command "_.CYLINDER" (list x y z) r h)
 (entlast)
)
(defun cut (e) (command "_.SUBTRACT" body "" e ""))
(defun addsolid (e) (command "_.UNION" body e "") (setq body (entlast)))
(defun getbody () (ssname (ssget "_X" '((0 . "3DSOLID"))) 0))
(defun xcyl (x y z r h / e)
 (setq e (cyl 0 0 0 r h))
 (command "_.ROTATE3D" e "" "_Yaxis" '(0 0 0) 90)
 (command "_.MOVE" e "" '(0 0 0) (list x y z))
 e
)

(setq body (getbody))
(addsolid (xcyl 130 -88 40 19 9.7))
(setq rib (prism '((-49 -88 0) (-49 -64.8 -1) (-31 -64.8 0) (-31 -88 -1)) 0 5))
(command "_.ROTATE3D" rib "" "_Yaxis" '(0 0 0) 90)
(command "_.MOVE" rib "" '(0 0 0) (list 132.7 0 0))
(addsolid rib)
(setq rib (prism '((-40 -55.7 0) (0 -12.8 0) (0 -6 0) (-40 -48.9 0)) 0 3.5))
(command "_.ROTATE3D" rib "" "_Yaxis" '(0 0 0) 90)
(command "_.MOVE" rib "" '(0 0 0) (list 133.2 0 0))
(addsolid rib)
(setq rib (prism '((-40 -55.7 0) (-80 -12.8 0) (-80 -6 0) (-40 -48.9 0)) 0 3.5))
(command "_.ROTATE3D" rib "" "_Yaxis" '(0 0 0) 90)
(command "_.MOVE" rib "" '(0 0 0) (list 133.2 0 0))
(addsolid rib)
(setq rib (prism '((0 -90.5 0) (0 -85.5 0) (-80 -85.5 0) (-80 -90.5 0)) 0 3.5))
(command "_.ROTATE3D" rib "" "_Yaxis" '(0 0 0) 90)
(command "_.MOVE" rib "" '(0 0 0) (list 133.2 0 0))
(addsolid rib)
(cut (xcyl 70 32 40 18 80))
(cut (xcyl 124.7 32 40 23 20))
(cut (xcyl 70 -88 40 9.5 80))
(cut (xcyl 137.2 -88 40 14.5 5))
(cut (xcyl -132 0 40 13 4.1))
(cut (xcyl -132 0 40 7.75 13.3))
(cut (xcyl -132 0 40 5.5 29.1))
(cut (xcyl -132 0 40 4 44))
(cut (xcyl -132 -55.8 40 13 4.1))
(cut (xcyl -132 -55.8 40 5.5 13.3))
(cut (xcyl -132 -55.8 40 4 30.1))
(cut (xcyl -132 -55.8 40 2 44))
(cut (xcyl -132 -127.9 15 3.0 33))
(cut (xcyl -132 -127.9 59.1 3.0 33))
(princ "\nSTAGE03_PORTS_DONE")


(setvar "CMDECHO" 0)
(setvar "FILEDIA" 0)
(setvar "OSMODE" 0)
(setvar "INSUNITS" 4)
(setvar "DELOBJ" 1)
(setvar "FACETRES" 10)
(setvar "ISOLINES" 0)
(defun poly (vs z / data v)
 (setq data (list '(0 . "LWPOLYLINE") '(100 . "AcDbEntity") '(100 . "AcDbPolyline") (cons 90 (length vs)) '(70 . 1) (cons 38 z)))
 (foreach v vs (setq data (append data (list (cons 10 (list (car v) (cadr v))) (cons 42 (caddr v))))))
 (entmakex data)
)
(defun prism (vs z h / e)
 (setq e (poly vs z))
 (command "_.EXTRUDE" e "" h)
 (entlast)
)
(defun cyl (x y z r h / e)
 (command "_.CYLINDER" (list x y z) r h)
 (entlast)
)
(defun cut (e) (command "_.SUBTRACT" body "" e ""))
(defun addsolid (e) (command "_.UNION" body e "") (setq body (entlast)))
(defun getbody () (ssname (ssget "_X" '((0 . "3DSOLID"))) 0))
(defun xcyl (x y z r h / e)
 (setq e (cyl 0 0 0 r h))
 (command "_.ROTATE3D" e "" "_Yaxis" '(0 0 0) 90)
 (command "_.MOVE" e "" '(0 0 0) (list x y z))
 e
)

(setq body (getbody))
(setq groove (prism '((97.5 0 1) (-97.5 0 0) (-97.5 -55.8 1) (97.5 -55.8 0)) -0.1 1.6))
(setq inner (prism '((95.5 0 1) (-95.5 0 0) (-95.5 -55.8 1) (95.5 -55.8 0)) -0.2 1.8))
(command "_.SUBTRACT" groove "" inner "")
(cut groove)
(setq groove (prism '((126 0 1) (-126 0 0) (-126 -55.8 1) (126 -55.8 0)) -0.1 1.6))
(setq inner (prism '((124.5 0 1) (-124.5 0 0) (-124.5 -55.8 1) (124.5 -55.8 0)) -0.2 1.8))
(command "_.SUBTRACT" groove "" inner "")
(cut groove)
(setq groove (prism '((97.5 0 1) (-97.5 0 0) (-97.5 -55.8 1) (97.5 -55.8 0)) 78.5 1.6))
(setq inner (prism '((95.5 0 1) (-95.5 0 0) (-95.5 -55.8 1) (95.5 -55.8 0)) 78.4 1.8))
(command "_.SUBTRACT" groove "" inner "")
(cut groove)
(setq groove (prism '((126 0 1) (-126 0 0) (-126 -55.8 1) (126 -55.8 0)) 78.5 1.6))
(setq inner (prism '((124.5 0 1) (-124.5 0 0) (-124.5 -55.8 1) (124.5 -55.8 0)) 78.4 1.8))
(command "_.SUBTRACT" groove "" inner "")
(cut groove)
(cut (prism '((-43.5 -194 0) (-40.5 -194 0) (-40.5 -189.9 0) (-43.5 -189.9 0)) -1 82))
(cut (prism '((-35.5 -194 0) (-32.5 -194 0) (-32.5 -189.9 0) (-35.5 -189.9 0)) -1 82))
(cut (prism '((-27.5 -194 0) (-24.5 -194 0) (-24.5 -189.9 0) (-27.5 -189.9 0)) -1 82))
(cut (prism '((-19.5 -194 0) (-16.5 -194 0) (-16.5 -189.9 0) (-19.5 -189.9 0)) -1 82))
(cut (prism '((-11.5 -194 0) (-8.5 -194 0) (-8.5 -189.9 0) (-11.5 -189.9 0)) -1 82))
(cut (prism '((-3.5 -194 0) (-0.5 -194 0) (-0.5 -189.9 0) (-3.5 -189.9 0)) -1 82))
(cut (prism '((4.5 -194 0) (7.5 -194 0) (7.5 -189.9 0) (4.5 -189.9 0)) -1 82))
(cut (prism '((12.5 -194 0) (15.5 -194 0) (15.5 -189.9 0) (12.5 -189.9 0)) -1 82))
(cut (prism '((20.5 -194 0) (23.5 -194 0) (23.5 -189.9 0) (20.5 -189.9 0)) -1 82))
(cut (prism '((28.5 -194 0) (31.5 -194 0) (31.5 -189.9 0) (28.5 -189.9 0)) -1 82))
(cut (prism '((36.5 -194 0) (39.5 -194 0) (39.5 -189.9 0) (36.5 -189.9 0)) -1 82))
(command "_.CHPROP" body "" "_Color" "8" "")
(command "_.VPOINT" (list 1 -1 1.35))
(command "_.ZOOM" "_Extents")
(princ "\nSTAGE04_FACE_DETAILS_DONE")
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
