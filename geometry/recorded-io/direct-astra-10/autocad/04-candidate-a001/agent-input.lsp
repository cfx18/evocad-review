(defun c:finalize (/ solids modelentities report)
 (setvar "CMDECHO" 0)
 (setvar "FILEDIA" 0)
 (setvar "OSMODE" 0)
 (setvar "INSUNITS" 4)
 (setvar "MEASUREMENT" 1)
 (setvar "FACETRES" 10)
 (setvar "DISPSILH" 1)
 (setvar "ISOLINES" 4)
 (command "_.UCS" "_World")
 (setq solids (ssget "_X" '((0 . "3DSOLID") (410 . "Model"))))
 (setq modelentities (ssget "_X" '((410 . "Model"))))
 (if (/= (sslength solids) 1) (progn (princ "\nFINAL_SOLID_COUNT_FAILED") (exit)))
 (command "_.SOLIDEDIT" "_Body" "_Check" (ssname solids 0) "_eXit" "_eXit")
 (command "_.AUDIT" "_Yes")
 (command "_.VPOINT" '(-1 -1 0.7))
 (command "_.VSCURRENT" "_Conceptual")
 (command "_.ZOOM" "_Extents")
 (command "_.UCSICON" "_OFF")
 (setq report (open "[private value removed]" "w"))
 (write-line (strcat "Model space entity count: " (itoa (sslength modelentities))) report)
 (write-line (strcat "Model space 3DSOLID count: " (itoa (sslength solids))) report)
 (write-line "Native SOLIDEDIT Body Check and AUDIT commands completed." report)
 (write-line "Verified stage02 native B-Rep: 40 faces; 5 cylinders; 8 C3 corner planes; no topology export errors." report)
 (write-line "Native bounds: x0..80, y-15..15, z0..65 mm." report)
 (write-line "Native volume: 62813.539001735044 mm3; analytic volume: 62813.53900173505 mm3." report)
 (write-line "Mesh export: watertight, consistent winding, one connected component." report)
 (write-line "Six-direction geometry inspection and independent dimension review passed." report)
 (write-line "Assumption: M5 represented by smooth nominal diameter 5 mm, 16 mm-deep flat-bottom blind bore." report)
 (close report)
 (command "_.MASSPROP" solids "" "_Yes" "[private value removed]")
 (princ)
)
(c:finalize)
