(vl-load-com)
(setvar "CMDECHO" 0)
(setvar "FILEDIA" 0)
(setvar "OSMODE" 0)
(setvar "INSUNITS" 4)
(setvar "DELOBJ" 1)
(setvar "FACETRES" 10)
(setvar "ISOLINES" 0)
(defun poly (vs z / data v)
 (setq data (list '(0 . "LWPOLYLINE") '(100 . "AcDbEntity") '(100 . "AcDbPolyline") (cons 90 (length vs)) '(70 . 1) (cons 38 z)))
 (foreach v vs (setq data (append data (list (cons 10 (list (car v) (cadr v))) (cons 42 (caddr v))))))
 (entmakex data)
)
(defun prism (vs z h / e)
 (setq e (poly vs z))
 (command "_.EXTRUDE" e "" h)
 (entlast)
)
(defun cyl (x y z r h / e)
 (command "_.CYLINDER" (list x y z) r h)
 (entlast)
)
(defun cut (e) (command "_.SUBTRACT" body "" e ""))
(defun addsolid (e) (command "_.UNION" body e "") (setq body (entlast)))
(defun getbody () (ssname (ssget "_X" '((0 . "3DSOLID"))) 0))
(defun xcyl (x y z r h / e)
 (setq e (cyl 0 0 0 r h))
 (command "_.ROTATE3D" e "" "_Yaxis" '(0 0 0) 90)
 (command "_.MOVE" e "" '(0 0 0) (list x y z))
 e
)

(setq body (getbody))
(setq groove (prism '((97.5 0 1) (-97.5 0 0) (-97.5 -55.8 1) (97.5 -55.8 0)) -0.1 1.6))
(setq inner (prism '((95.5 0 1) (-95.5 0 0) (-95.5 -55.8 1) (95.5 -55.8 0)) -0.2 1.8))
(command "_.SUBTRACT" groove "" inner "")
(cut groove)
(setq groove (prism '((126 0 1) (-126 0 0) (-126 -55.8 1) (126 -55.8 0)) -0.1 1.6))
(setq inner (prism '((124.5 0 1) (-124.5 0 0) (-124.5 -55.8 1) (124.5 -55.8 0)) -0.2 1.8))
(command "_.SUBTRACT" groove "" inner "")
(cut groove)
(setq groove (prism '((97.5 0 1) (-97.5 0 0) (-97.5 -55.8 1) (97.5 -55.8 0)) 78.5 1.6))
(setq inner (prism '((95.5 0 1) (-95.5 0 0) (-95.5 -55.8 1) (95.5 -55.8 0)) 78.4 1.8))
(command "_.SUBTRACT" groove "" inner "")
(cut groove)
(setq groove (prism '((126 0 1) (-126 0 0) (-126 -55.8 1) (126 -55.8 0)) 78.5 1.6))
(setq inner (prism '((124.5 0 1) (-124.5 0 0) (-124.5 -55.8 1) (124.5 -55.8 0)) 78.4 1.8))
(command "_.SUBTRACT" groove "" inner "")
(cut groove)
(cut (prism '((-43.5 -194 0) (-40.5 -194 0) (-40.5 -189.9 0) (-43.5 -189.9 0)) -1 82))
(cut (prism '((-35.5 -194 0) (-32.5 -194 0) (-32.5 -189.9 0) (-35.5 -189.9 0)) -1 82))
(cut (prism '((-27.5 -194 0) (-24.5 -194 0) (-24.5 -189.9 0) (-27.5 -189.9 0)) -1 82))
(cut (prism '((-19.5 -194 0) (-16.5 -194 0) (-16.5 -189.9 0) (-19.5 -189.9 0)) -1 82))
(cut (prism '((-11.5 -194 0) (-8.5 -194 0) (-8.5 -189.9 0) (-11.5 -189.9 0)) -1 82))
(cut (prism '((-3.5 -194 0) (-0.5 -194 0) (-0.5 -189.9 0) (-3.5 -189.9 0)) -1 82))
(cut (prism '((4.5 -194 0) (7.5 -194 0) (7.5 -189.9 0) (4.5 -189.9 0)) -1 82))
(cut (prism '((12.5 -194 0) (15.5 -194 0) (15.5 -189.9 0) (12.5 -189.9 0)) -1 82))
(cut (prism '((20.5 -194 0) (23.5 -194 0) (23.5 -189.9 0) (20.5 -189.9 0)) -1 82))
(cut (prism '((28.5 -194 0) (31.5 -194 0) (31.5 -189.9 0) (28.5 -189.9 0)) -1 82))
(cut (prism '((36.5 -194 0) (39.5 -194 0) (39.5 -189.9 0) (36.5 -189.9 0)) -1 82))
(command "_.CHPROP" body "" "_Color" "8" "")
(command "_.VPOINT" (list 1 -1 1.35))
(command "_.ZOOM" "_Extents")
(princ "\nSTAGE04_FACE_DETAILS_DONE")
(setvar "CMDECHO" 1)
(command "_.STLOUT" body "" "_Yes" "[private value removed]")
(princ "\nPREVIEW_EXPORT_DONE")
(setq mcp-handles-file (open "[private value removed]" "w"))
(if (setq mcp-solids (ssget "_X" '((0 . "3DSOLID"))))
  (progn (setq mcp-index 0) (repeat (sslength mcp-solids)
    (write-line (cdr (assoc 5 (entget (ssname mcp-solids mcp-index)))) mcp-handles-file)
    (setq mcp-index (1+ mcp-index)))))
(close mcp-handles-file)
(command "_.QSAVE")
(setq mcp-success-file (open "[private value removed]" "w"))
(write-line "ok" mcp-success-file)
(close mcp-success-file)
(princ)
